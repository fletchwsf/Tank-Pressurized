# Specification modules for tank-pressurized

# Specification: Specification Document
- Description: CSR Customer requirements

## CSR-001
The pressurized tank module shall contain the following sub-assemblies
- Rational: Customer defined component

### R3
Tank
- Type: Essential

### R6
Control Panel
- Type: Derived

### R5
Motor-Electrical
- Type: Essential

### R4
Pump
- Type: Essential

## R2
Safety requirements
- Type: Heading

### R7
Pressurization switch
- Rational: Customer defined component
- Type: Essential
