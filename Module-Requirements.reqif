# Specification: Specification Document

## R1
Pressure switch

### R8
The pressure switch will open or close an electrical contact based on a pressure signal exceeding the set point of the switch.

### R2
Input

#### R9
The pressure switch shall accept a fluid input pressure input between <<Minimum Working pressure>> and <<Maximum Working pressue>>.

#### R13
The pressure switch shall accept a single electrical input.

### R3
Processing

#### R10
When the fluid pressure is less than <<Set Point>> minus <<tolerence>> the electrical contact shall be open.

#### R11
When the fluid pressure is greater than <<Set Point>> plus <<tolerence>> the electrical contact shall be closed.

#### R12
When the fluid pressure is between <<Set Point>> minus <<tolerence>> and <<Set Point>> plus tolerence, the electrical contact shall be open or closed.

#### R25
The electrical contacts shall open or close within 1 milli-second.

### R4
Output

#### R14
The pressure switch shall provide a single electrical output.

#### R15
When the electrical contact is closed, the input shall be connected to the output.

#### R16
When the electical contact is open, the output shall be disconnected from the input.

### R5
Safety Requirements

#### R6
The pressure switch shall withstand pressures upto 2 times <<Maximum Working pressure>> with no mechanical or electrical failures.

#### R17
The pressure switch shall withstand electrical voltage upto 100 times <<Maximum Input voltage>> with no electrical failures.

### R18
Failure Modes

#### R19
Electrical contacts stuck open

#### R20
Electrical contacts stuck closed

#### R21
Electrical contacts open too late

#### R22
Electircal contancts open too soon

#### R23
Electrical contacts close too soon

#### R24
Electrical contacts close too late

#### R26
Fluid leak reduces sensor signal pressure

#### R27
Fluid leak contaminates electrical contact

#### R28
Fluid leak into environment

## R7
Start Switch

## R29
Pressure tank

## R30
Valve-Outlet

## R31
Pump

## R32
Motor

## R33
Timer relay

## R34
Fuse

### R35
The electrical motor and pressurization controller shall be supplied electrical power through a fuse with a current rating of <<maximum current>>

### R41
Inputs

#### R43
The fuse shall accept a 220 Volt AC input.

### R37
Processing

#### R45
When the current flow through the fuse exceeeds <<maximum current>> for more than <<fuse time>> milli-seconds the fuse contacts shall be permanently open.

### R38
Outputs

#### R44
When the fuse is closed, the fuse shall connect the input to the output.

## R42

## R36
Inputs

## R39
Outputs

## R40
The fuse shall accept a standard 220 Volt AC input.
